module cop-topology {

    yang-version 1;

    namespace "urn:ietf:params:xml:ns:yang:cop-topology";

    prefix cop-topology;

    import cop-call {
        prefix cop-call;
    }

    organization "CTTC";

    description "YANG version of the Common Orchestration Protocol (COP).";

    revision "2017-01-12" {
        description
        "Service Topology module for 5G-Crosshaul";
    }

    typedef topology-ref {
        type leafref {
            path "/context/topology/topology_id";
        }
        description
            "A type for an absolute reference a topology instance.";
    }

    typedef edge_type_enumeration {
        type enumeration {
            enum dwdm_edge {
                value 1;
                description "DWDM link";
            }
            enum eth_edge {
                value 2;
                description "Ethernet link";
            }
            enum wireless_edge {
                value 3;
                description "Wireless Ethernet link";
            }
        }
    }

    typedef node_type_enumeration {
        type enumeration {
            enum OF {
                value 0;
                description "OpenFlow node";
            }        
            enum GMPLS {
                value 1;
                description "GMPLS node";
            }
            enum OF-W {
                value 2;
                description "OpenFlow wireless node";
            }
            enum ABSTRACT {
                value 3;
                description "Abstract node";
            }
            enum OF-IOT {
                value 4;
                description "IoT node";
            }
            enum HOST {
                value 5;
                description "Host node";
            }
        }
    }

    typedef switching_cap_enumeration {
        type enumeration {
            enum lsc {
                value 1;
                description "Label Switching Capability sw_cap";
            }
            enum psc {
                value 2;
                description "Packet Switching Capability sw_cap";
            }
        }
    }

    typedef node_id_type_enumeration{
        type enumeration{
            enum IPv4 {
                value 0;
                description "xxx.yyy.zzz.www";
            }
            enum IPv6 {
                value 1;
            }
            enum DatapathID {
                value 2;
                description "AA:BB:CC:DD:EE:FF:00:01";
            }
            enum MAC {
                value 3;
                description "AA:BB:CC:DD:EE:FF";
            }
        }
    }

    grouping topology{
        leaf topology_id{
            type string;
        }
        leaf-list underlay-topology {
            description "List of topologies from which this depends on.";
            type topology-ref;
        }
        list nodes{
            config false;
            key "node_id";
            uses node;
        }
        list edges{
            config false;
            key "edge_id";
            uses edge;
        }
    }

    grouping edge_end{
        leaf edge_end_id{
            type string;
        }
        leaf switching_cap{
            type switching_cap_enumeration;
        }
        leaf name{
            type string;
        }
        leaf peer_node_id{
            type string;
        }
    }

    grouping node{
        leaf node_id{
            type string;
        }
        leaf node_id_type{
            type node_id_type_enumeration;
        }
        leaf-list underlay-abstract-topology{
            description "List of topology_ids which are represented by this node.";
            type topology-ref;
        }
        leaf name{
            type string;
        }
        leaf domain{
            type string;
        }
        list edge_end{
            key "edge_end_id";
            uses edge_end;
        }
        leaf nodetype {
            type node_type_enumeration;
        }
    }

    grouping edge{
        leaf edge_type{
            mandatory true;
            type edge_type_enumeration;
	      }
        leaf edge_id{
            mandatory true;
            type string;
        }
        leaf name{
            type string;
        }
        leaf switching_cap{
            mandatory true;
            type string;
        }
        leaf metric{
            type string;
        }
        leaf max_resv_bw{
            type string;
        }
        leaf unreserv_bw{
            type string;
        }
        leaf latency{
            type string;
        }
        leaf source{
            type leafref {
              path '/context/topology/nodes/node_id';
            }
        }
        leaf target{
            type leafref {
              path '/context/topology/nodes/node_id';
            }
        }
        leaf local_ifid{
            type leafref {
              path '/context/topology/nodes/edge_end/edge_end_id';
            }
        }
        leaf remote_ifid{
            type leafref {
              path '/context/topology/nodes/edge_end/edge_end_id';
            }
        }
    }

    grouping dwdm_channel{
        leaf g694_id{
            type int32;
        }
        leaf state{
            type int32;
        }
    }

    grouping bitmap{
        leaf numChannels{
            type int16;
        }
        leaf-list arrayBits{
            type int16;
        }
    }

    grouping dwdm_edge{
        container bitmap{
            uses bitmap;
        }
        list channels{
            key "g694_id";
            uses dwdm_channel;
        }
        uses edge;
    }
    
    grouping eth_edge{
        uses edge;
    }
    
    grouping wireless_edge{
        uses edge;
    }

    
    container context{
        config false;
        leaf context_id{
            type string;
        }
        leaf provider{
            type boolean;
            default false;
        }
        leaf parent_context{
            type leafref{
                path '/context/context_id';
            }
        }
        list topology{
            key "topology_id";
            uses topology;
        }
        list service_endpoint{
            key "endpoint_id";
            uses cop-call:service-endpoint;
        }
    }
    grouping notification_edge_end_object{
        leaf node_id{
	    type leafref {
              path '/context/topology/nodes/node_id';
            }
	}
	container edge_end{
	    uses edge_end;
	}
	
    }
    
    notification remove_edge{
        uses edge;
    }
    notification add_edge{
        uses edge;
    }
    notification remove_edgeEnd{
        uses notification_edge_end_object;
    }
    notification add_edgeEnd{
        uses notification_edge_end_object;
    }
    notification remove_node{
        uses node;
    }
    notification add_node{
        uses node;
    }
    notification update_topology{
        uses topology;
    }
}
