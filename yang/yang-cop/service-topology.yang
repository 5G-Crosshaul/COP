module service-topology {

    yang-version 1;

    namespace "urn:ietf:params:xml:ns:yang:service-topology";

    prefix s-topology;

    organization "CTTC";

    description "YANG version of the Common Orchestration Protocol (COP).";

    revision "2016-12-02" {
        description
        "Service Topology module for 5G-Crosshaul";
    }

    typedef topology-ref {
        type leafref {
            path "/topologies/topology/topology_id";
        }
        description
            "A type for an absolute reference a topology instance.";
    }

    typedef edge_type_enumeration {
        type enumeration {
            enum dwdm_edge {
                value 1;
                description "DWDM link";
            }
            enum eth_edge {
                value 2;
                description "Ethernet link";
            }
            enum wireless_edge {
                value 3;
                description "Wireless Ethernet link";
            }
        }
    }

    typedef switching_cap_enumeration {
        type enumeration {
            enum lsc {
                value 1;
                description "Label Switching Capability sw_cap";
            }
            enum psc {
                value 2;
                description "Packet Switching Capability sw_cap";
            }
        }
    }

    grouping topology{
        leaf topology_id{
            type string;
        }
        leaf-list underlay-topology {
            description "List of topologies from which this depends on.";
            type topology-ref;
        }
        list nodes{
            config false;
            key "node_id";
            uses node;
        }
        list edges{
            config false;
            key "edge_id";
            uses edge;
        }
        container topology_types{
            description "Empty container used to be augmented with one or more empty optional
                    container to indicate the topology type(s)";
        }
    }

    grouping edge_end{
        leaf edge_end_id{
            type string;
        }
        leaf switching_cap{
            type switching_cap_enumeration;
        }
        leaf name{
            type string;
        }
        leaf peer_node_id{
            type string;
        }
    }

    grouping node{
        leaf node_id{
            type string;
        }
        leaf-list underlay-abstract-topology{
            description "List of topology_ids which are represented by this node.";
            type topology-ref;
        }
        leaf name{
            type string;
        }
        leaf domain{
            type string;
        }
        container node_type{
            description "Empty container used to be augmented with  a new empty optional
                    container to indicate the new Node Type";
        }
        list edge_end{
            key "edge_end_id";
            uses edge_end;
        }
    }

    grouping edge{
        leaf edge_type{
            mandatory true;
            type edge_type_enumeration;
	      }
        leaf edge_id{
            mandatory true;
            type string;
        }
        leaf name{
            type string;
        }
        leaf switching_cap{
            mandatory true;
            type string;
        }
        leaf metric{
            type string;
        }
        leaf max_resv_bw{
            type string;
        }
        leaf unreserv_bw{
            type string;
        }
        leaf latency{
            type string;
        }
        container source{
            uses node;
        }
        container target{
            uses node;
        }
        container local_ifid{
            uses edge_end;
        }
        container remote_ifid{
            uses edge_end;
        }
    }

    grouping dwdm_channel{
        leaf g694_id{
            type int32;
        }
        leaf state{
            type int32;
        }
    }

    grouping bitmap{
        leaf numChannels{
            type int16;
        }
        leaf-list arrayBits{
            type int16;
        }
    }

    grouping dwdm_edge{
        container bitmap{
            uses bitmap;
        }
        list channels{
            key "g694_id";
            uses dwdm_channel;
        }
        uses edge;
    }
    
    grouping eth_edge{
        uses edge;
    }
    
    grouping service_end_point_type{
        leaf sep_id{
            type string;
        }
        leaf name{
            type string;
        }
        leaf edge_end_id{
            type string;
        }
        leaf node_id{
            type string;
        }
    }
    
    container topologies{
        config false;
        list topology{
            key "topology_id";
            uses topology;
        }
        list service_end_point{
            key "sep_id";
            uses service_end_point_type;
        }
    }

}
